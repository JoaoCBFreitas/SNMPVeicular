OBU-MIB DEFINITIONS ::= BEGIN

IMPORTS
	experimental,
	MODULE-IDENTITY,
	OBJECT-TYPE,
	Counter32,
	Unsigned32
		FROM SNMPv2-SMI
	TEXTUAL-CONVENTION
		FROM SNMPv2-TC
	OBJECT-GROUP
		FROM SNMPv2-CONF;

obuMIB MODULE-IDENTITY
	LAST-UPDATED "202103121429Z"	-- Mar 12, 2021, 2:29:00 PM
	ORGANIZATION "Universidade do Minho"
	CONTACT-INFO
		""
	DESCRIPTION
		"SMIv2 MIB module to be used in vehicular OBU"
	REVISION "202103121429Z"	-- Mar 12, 2021, 2:29:00 PM
	DESCRIPTION
		"Initial version."
	-- 1.3.6.1.3.8888 --
::= { experimental 8888 }

requestMonitoringDataTable OBJECT-TYPE
	SYNTAX  SEQUENCE OF RequestMonitoringDataEntry
	MAX-ACCESS not-accessible
	STATUS  current
	DESCRIPTION
		"This table will list all information regarding a requests on a specific object."
	-- 1.3.6.1.3.8888.1
::= { obuMIB 1 }

requestMonitoringDataEntry OBJECT-TYPE
	SYNTAX  RequestMonitoringDataEntry
	MAX-ACCESS not-accessible
	STATUS  current
	DESCRIPTION ""
	INDEX {
		requestID }
	-- 1.3.6.1.3.8888.1.1
::= { requestMonitoringDataTable 1 }


RequestMonitoringDataEntry ::= SEQUENCE {

	requestID         	Unsigned32,
	requestMonControlID  	Unsigned32,
	requestMapID      	Unsigned32,
	requestStatisticsID 	Unsigned32,
	savingMode        	INTEGER,
	samplingFrequency 	Unsigned32,
	maxDelay          	INTEGER,
	startTime         	OBUDateandTime,
	endTime           	OBUDateandTime,
	waitTime			OBUDateandTime,
	durationTime      	OBUDateandTime,
	expireTime        	OBUDateandTime,
	lastSampleID      	Unsigned32,
	nOfSamples        	Counter32,
	maxNOfSamples		Unsigned32,
	loopMode		INTEGER,
	status            	INTEGER,
	requestUser         	OCTET STRING}

requestID OBJECT-TYPE
	SYNTAX  Unsigned32 (1..99999999)
	MAX-ACCESS read-create
	STATUS  current
	DESCRIPTION
		"This object will identify an individual request"
	-- 1.3.6.1.3.8888.1.1.1
::= { requestMonitoringDataEntry 1 }

requestMonControlID OBJECT-TYPE
	SYNTAX  Unsigned32
	MAX-ACCESS read-create
	STATUS  current
	DESCRIPTION
		"This object will identify the requestControlDataEntry related to a request"
	-- 1.3.6.1.3.8888.1.1.2
::= { requestMonitoringDataEntry 2 }

requestMapID OBJECT-TYPE
	SYNTAX  Unsigned32
	MAX-ACCESS read-create
	STATUS  current
	DESCRIPTION
		"This object will identify the mapTypeTable related to a requests"
	-- 1.3.6.1.3.8888.1.1.3
::= { requestMonitoringDataEntry 3 }

requestStatisticsID OBJECT-TYPE
	SYNTAX  Unsigned32
	MAX-ACCESS read-create
	STATUS  current
	DESCRIPTION
		"This object will identify the requestStatisticsDataEntry related to a request"
	-- 1.3.6.1.3.8888.1.1.4
::= { requestMonitoringDataEntry 4 }

savingMode OBJECT-TYPE
	SYNTAX  INTEGER {
			permanent(0),
			volatile(1) }
	MAX-ACCESS read-create
	STATUS  current
	DESCRIPTION
		"This object will identify the mode in which a specific request will be saved"
	-- 1.3.6.1.3.8888.1.1.5
::= { requestMonitoringDataEntry 5 }


samplingFrequency OBJECT-TYPE
	SYNTAX  Unsigned32
	MAX-ACCESS read-create
	STATUS  current
	DESCRIPTION
		"This object will store the sampling frequency"
	-- 1.3.6.1.3.8888.1.1.6
::= { requestMonitoringDataEntry 6 }


maxDelay OBJECT-TYPE
	SYNTAX  INTEGER
	MAX-ACCESS read-create
	STATUS  current
	DESCRIPTION
		"This object will store the maximum delay allowed"
	-- 1.3.6.1.3.8888.1.1.7
::= { requestMonitoringDataEntry 7 }


startTime OBJECT-TYPE
	SYNTAX  OBUDateandTime
	MAX-ACCESS read-create
	STATUS  current
	DESCRIPTION
		"This object will store the start time of a certain request"
	-- 1.3.6.1.3.8888.1.1.8
::= { requestMonitoringDataEntry 8}


endTime OBJECT-TYPE
	SYNTAX  OBUDateandTime
	MAX-ACCESS read-create
	STATUS  current
	DESCRIPTION
		"This object will store the end time of a certain request"
	-- 1.3.6.1.3.8888.1.1.9
::= { requestMonitoringDataEntry 9 }

waitTime OBJECT-TYPE
	SYNTAX  OBUDateandTime
	MAX-ACCESS read-create
	STATUS  current
	DESCRIPTION
		"This object will store the wait time of a certain request"
	-- 1.3.6.1.3.8888.1.1.10 --
	::= { requestMonitoringDataEntry 10 }

durationTime OBJECT-TYPE
	SYNTAX  OBUDateandTime
	MAX-ACCESS read-create
	STATUS  current
	DESCRIPTION
		"This object will store the duration time of a certain request"
	-- 1.3.6.1.3.8888.1.1.11
::= { requestMonitoringDataEntry 11}


expireTime OBJECT-TYPE
	SYNTAX  OBUDateandTime
	MAX-ACCESS read-create
	STATUS  current
	DESCRIPTION
		"This object will store the expire time of a certain request"
	-- 1.3.6.1.3.8888.1.1.12
::= { requestMonitoringDataEntry 12}


lastSampleID OBJECT-TYPE
	SYNTAX  Unsigned32
	MAX-ACCESS read-create
	STATUS  current
	DESCRIPTION
		"This object will store the ID of the last sample to be recorded"
	-- 1.3.6.1.3.8888.1.1.13
::= { requestMonitoringDataEntry 13 }


nOfSamples OBJECT-TYPE
	SYNTAX  Counter32
	MAX-ACCESS read-create
	STATUS  current
	DESCRIPTION
		"This object will store the total number of samples recorded"
	-- 1.3.6.1.3.8888.1.1.14
::= { requestMonitoringDataEntry 14 }

maxNOfSamples OBJECT-TYPE
	SYNTAX  Unsigned32
	MAX-ACCESS read-create
	STATUS  current
	DESCRIPTION
		"This object will store the max number of samples to be recorded for a request"
	-- 1.3.6.1.3.8888.1.1.15
::= { requestMonitoringDataEntry 15 }

loopMode OBJECT-TYPE
	SYNTAX  INTEGER {
			yes(1),
			no(2)}
	MAX-ACCESS read-only
	STATUS  current
	DESCRIPTION
		"This object will identify whether the request will loop or not"
	-- 1.3.6.1.3.8888.1.1.16
::= { requestMonitoringDataEntry 16 }

status OBJECT-TYPE
	SYNTAX  INTEGER {
			off(0),
			on(1),
			set(2),
			delete(3),
			ready(4) }
	MAX-ACCESS read-only
	STATUS  current
	DESCRIPTION
		"This object will identify the current status of a request"
	-- 1.3.6.1.3.8888.1.1.17
::= { requestMonitoringDataEntry 17 }

requestUser OBJECT-TYPE
	SYNTAX  OCTET STRING
	MAX-ACCESS read-create
	STATUS  current
	DESCRIPTION
		"This object will store the expire time of a certain request"
	-- 1.3.6.1.3.8888.1.1.18
::= { requestMonitoringDataEntry 18}


requestControlDataTable OBJECT-TYPE
	SYNTAX  SEQUENCE OF RequestControlDataEntry
	MAX-ACCESS not-accessible
	STATUS  current
	DESCRIPTION
		"This table is used to identify and store information regarding all requests on an object."
	-- 1.3.6.1.3.8888.2
::= { obuMIB 2 }


requestControlDataEntry OBJECT-TYPE
	SYNTAX  RequestControlDataEntry
	MAX-ACCESS not-accessible
	STATUS  current
	DESCRIPTION
		""
	INDEX {
		requestControlID }
	-- 1.3.6.1.3.8888.2.1
	::= { requestControlDataTable 1 }


RequestControlDataEntry ::= SEQUENCE {

	requestControlID    Unsigned32,
	requestControlMapID Unsigned32,
	settingMode         INTEGER,
	commitTime          OBUDateandTime,
	endControlTime      OBUDateandTime,
	durationControlTime OBUDateandTime,
	expireControlTime   OBUDateandTime,
	valuesTableID       Unsigned32,
	statusControl       INTEGER }

requestControlID OBJECT-TYPE
	SYNTAX  Unsigned32 (1..99999999)
	MAX-ACCESS read-only
	STATUS  current
	DESCRIPTION
		"ID of a certain request"
	-- 1.3.6.1.3.8888.2.1.1
::= { requestControlDataEntry 1 }

requestControlMapID OBJECT-TYPE
	SYNTAX  Unsigned32
	MAX-ACCESS read-only
	STATUS  current
	DESCRIPTION
		"This object will identify the requestControlMapID related to a certain request"
	-- 1.3.6.1.3.8888.2.1.2 --
	::= { requestControlDataEntry 2 }

settingMode OBJECT-TYPE
	SYNTAX  INTEGER {
			permanent(0),
			volatile(1) }
	MAX-ACCESS read-only
	STATUS  current
	DESCRIPTION
		"This object will identify the mode in which a specific request will be set"
	-- 1.3.6.1.3.8888.2.1.3 --
	::= { requestControlDataEntry 3 }


commitTime OBJECT-TYPE
	SYNTAX  OBUDateandTime
	MAX-ACCESS read-only
	STATUS  current
	DESCRIPTION
		"This object will store the commit time of a certain request"
	-- 1.3.6.1.3.8888.2.1.4--
	::= { requestControlDataEntry 4 }

endControlTime OBJECT-TYPE
	SYNTAX  OBUDateandTime
	MAX-ACCESS read-only
	STATUS  current
	DESCRIPTION
		"This object will store the end time of a certain request"
	-- 1.3.6.1.3.8888.2.1.5 --
	::= { requestControlDataEntry 5 }


durationControlTime OBJECT-TYPE
	SYNTAX  OBUDateandTime
	MAX-ACCESS read-only
	STATUS  current
	DESCRIPTION
		"This object will store the duration time of a certain request"
	-- 1.3.6.1.3.8888.2.1.6 --
	::= { requestControlDataEntry 6 }


expireControlTime OBJECT-TYPE
	SYNTAX  OBUDateandTime
	MAX-ACCESS read-only
	STATUS  current
	DESCRIPTION
		"This object will store the expire time of a certain request"
	-- 1.3.6.1.3.8888.2.1.7 --
	::= { requestControlDataEntry 7 }


valuesTableID OBJECT-TYPE
	SYNTAX  Unsigned32
	MAX-ACCESS read-only
	STATUS  current
	DESCRIPTION
		"This object will identify the lastSampleID of the respective value related to a specific request"
	-- 1.3.6.1.3.8888.2.1.8 --
	::= { requestControlDataEntry 8 }

statusControl OBJECT-TYPE
	SYNTAX  INTEGER {
			inactive(0),
			active(1) }
	MAX-ACCESS read-only
	STATUS  current
	DESCRIPTION
		"This object will be used to check if there's any request on this object still active"
	-- 1.3.6.1.3.8888.2.1.9 --
	::= { requestControlDataEntry 9 }


requestStatisticsDataTable OBJECT-TYPE
	SYNTAX  SEQUENCE OF RequestStatisticsDataEntry
	MAX-ACCESS not-accessible
	STATUS  current
	DESCRIPTION
		"This table will be used to store relevant statistics regarding a certain request"
	-- 1.3.6.1.3.8888.3
::= { obuMIB 3 }

requestStatisticsDataEntry OBJECT-TYPE
	SYNTAX  RequestStatisticsDataEntry
	MAX-ACCESS not-accessible
	STATUS  current
	DESCRIPTION ""
	INDEX {
		statisticsID }
	-- 1.3.6.1.3.8888.3.1
::= { requestStatisticsDataTable 1 }


RequestStatisticsDataEntry ::= SEQUENCE {

	statisticsID           Unsigned32,
	durationTimeStatistics OBUDateandTime,
	nOfSamplesStatistics   Counter32,
	minValue               INTEGER,
	maxValue               INTEGER,
	avgValue               INTEGER }


statisticsID OBJECT-TYPE
	SYNTAX  Unsigned32 (1..99999999)
	MAX-ACCESS read-only
	STATUS  current
	DESCRIPTION
		"Statistics ID of a certain request"
	-- 1.3.6.1.3.8888.3.1.1
::= { requestStatisticsDataEntry 1 }

durationTimeStatistics OBJECT-TYPE
	SYNTAX  OBUDateandTime
	MAX-ACCESS read-only
	STATUS  current
	DESCRIPTION
		"This object will store the duration time of a certain request"
	-- 1.3.6.1.3.8888.3.1.2
::= { requestStatisticsDataEntry 2 }

nOfSamplesStatistics OBJECT-TYPE
	SYNTAX  Counter32
	MAX-ACCESS read-only
	STATUS  current
	DESCRIPTION
		"This object will store the number of samples recorded"
	-- 1.3.6.1.3.8888.3.1.3
::= { requestStatisticsDataEntry 3 }

minValue OBJECT-TYPE
	SYNTAX  INTEGER
	MAX-ACCESS read-only
	STATUS  current
	DESCRIPTION
		"Minimum value recorded by a certain request"
	-- 1.3.6.1.3.8888.3.1.4
::= { requestStatisticsDataEntry 4 }


maxValue OBJECT-TYPE
	SYNTAX  INTEGER
	MAX-ACCESS read-only
	STATUS  current
	DESCRIPTION
		"Maximum value recorded by a certain request"
	-- 1.3.6.1.3.8888.3.1.5
::= { requestStatisticsDataEntry 5 }


avgValue OBJECT-TYPE
	SYNTAX  INTEGER
	MAX-ACCESS read-only
	STATUS  current
	DESCRIPTION
		"Average value recorded by a certain request"
	-- 1.3.6.1.3.8888.3.1.6
::= { requestStatisticsDataEntry 6 }

capabilitiesTable OBJECT-TYPE
	SYNTAX  SEQUENCE OF CapabilitiesEntry
	MAX-ACCESS not-accessible
	STATUS  current
	DESCRIPTION
		"This table will list the vehicle/OBU capabilities, including all available services."
	-- 1.3.6.1.3.8888.4
::= { obuMIB 4 }


capabilitiesEntry OBJECT-TYPE
	SYNTAX  CapabilitiesEntry
	MAX-ACCESS not-accessible
	STATUS  current
	DESCRIPTION ""
	INDEX {
		capabilitiesID }
	-- 1.3.6.1.3.8888.4.1
::= { capabilitiesTable 1 }


CapabilitiesEntry ::= SEQUENCE {

	capabilitiesID         Unsigned32,
	setOfCapabilitiesID    Unsigned32,
	specificCapabilitiesID Unsigned32,
	capabilitieValue       OCTET STRING }

capabilitiesID OBJECT-TYPE
	SYNTAX  Unsigned32 (1..99999999)
	MAX-ACCESS read-only
	STATUS  current
	DESCRIPTION
		"This object will identify a capabilities table row"
	-- 1.3.6.1.3.8888.4.1.1
::= { capabilitiesEntry 1 }

setOfCapabilitiesID OBJECT-TYPE
	SYNTAX  Unsigned32
	MAX-ACCESS read-only
	STATUS  current
	DESCRIPTION "This column will identify capabilities relevant to a specific subsystem, e.g: Front Sensors"
	-- 1.3.6.1.3.8888.4.1.2
::= { capabilitiesEntry 2 }


specificCapabilitiesID OBJECT-TYPE
	SYNTAX  Unsigned32
	MAX-ACCESS read-only
	STATUS  current
	DESCRIPTION "This column will be used to indentify a specific capability"
	-- 1.3.6.1.3.8888.4.1.3
::= { capabilitiesEntry 3 }


capabilitieValue OBJECT-TYPE
	SYNTAX  OCTET STRING
	MAX-ACCESS read-only
	STATUS  current
	DESCRIPTION ""
	-- 1.3.6.1.3.8888.4.1.4
::= { capabilitiesEntry 4 }


samplesTable OBJECT-TYPE
	SYNTAX  SEQUENCE OF SamplesEntry
	MAX-ACCESS not-accessible
	STATUS  current
	DESCRIPTION
		"This table will store all values requested by a certain RequestSampleID which identifies the respective requestMonitoringDataTable."
	-- 1.3.6.1.3.8888.5
::= { obuMIB 5 }

samplesEntry OBJECT-TYPE
	SYNTAX  SamplesEntry
	MAX-ACCESS not-accessible
	STATUS  current
	DESCRIPTION
		""
	INDEX {
		sampleID }
	-- 1.3.6.1.3.8888.5.1
::= { samplesTable 1 }


SamplesEntry ::= SEQUENCE {

	sampleID            Unsigned32,
	requestSampleID     Unsigned32,
	timeStamp           OBUDateandTime,
	sampleFrequency     Unsigned32,
	previousSampleID    Unsigned32,
	sampleType          INTEGER,
	sampleRecordedValue INTEGER,
	mapTypeSamplesID    Unsigned32,
	sampleCheckSum      OCTET STRING }

sampleID OBJECT-TYPE
	SYNTAX  Unsigned32 (1..99999999)
	MAX-ACCESS read-only
	STATUS  current
	DESCRIPTION
		"This object will identify a specific recorded value"
	-- 1.3.6.1.3.8888.5.1.1
::= { samplesEntry 1 }


requestSampleID OBJECT-TYPE
	SYNTAX  Unsigned32
	MAX-ACCESS read-only
	STATUS  current
	DESCRIPTION
		"This object will be used to identify the request on requestControlDataTable"
	-- 1.3.6.1.3.8888.5.1.2
::= { samplesEntry 2 }

timeStamp OBJECT-TYPE
	SYNTAX  OBUDateandTime
	MAX-ACCESS read-only
	STATUS  current
	DESCRIPTION
		"This object will identify the time at which a value was recorded"
	-- 1.3.6.1.3.8888.5.1.3
::= { samplesEntry 3 }

sampleFrequency OBJECT-TYPE
	SYNTAX  Unsigned32
	MAX-ACCESS read-only
	STATUS  current
	DESCRIPTION
		"This object will store the sample frequency"
	-- 1.3.6.1.3.8888.5.1.4
::= { samplesEntry 4 }


previousSampleID OBJECT-TYPE
	SYNTAX  Unsigned32
	MAX-ACCESS read-only
	STATUS  current
	DESCRIPTION
		"This object will store the ID of the previously recorded sample from the same request"
	-- 1.3.6.1.3.8888.5.1.5
::= { samplesEntry 5 }

sampleType OBJECT-TYPE
	SYNTAX  INTEGER {
			short(0),
			medium(1),
			long(2) }
	MAX-ACCESS read-only
	STATUS  current
	DESCRIPTION
		"This object will store the type of data being recorded.
		short=16bit
		medium=32bit
		long=64bit"
	-- 1.3.6.1.3.8888.5.1.6 --
	::= { samplesEntry 6 }


sampleRecordedValue OBJECT-TYPE
	SYNTAX  INTEGER
	MAX-ACCESS read-only
	STATUS  current
	DESCRIPTION
		"This object will store sensor readings"
	-- 1.3.6.1.3.8888.5.1.7 --
	::= { samplesEntry 7 }


mapTypeSamplesID OBJECT-TYPE
	SYNTAX  Unsigned32
	MAX-ACCESS read-only
	STATUS  current
	DESCRIPTION
		"This object will point to the description of a signal."
	-- 1.3.6.1.3.8888.5.1.8 --
	::= { samplesEntry 8 }


sampleCheckSum OBJECT-TYPE
	SYNTAX  OCTET STRING
	MAX-ACCESS read-only
	STATUS  current
	DESCRIPTION
		"This object will be used to store a checksum of an recorded value, this checksum will be created based on timestamp and the name of the CAN node, and will so as to identify multiple readings from the same CAN message"
	-- 1.3.6.1.3.8888.5.1.9 --
	::= { samplesEntry 9 }

mapTypeTable OBJECT-TYPE
	SYNTAX  SEQUENCE OF MapTypeEntry
	MAX-ACCESS not-accessible
	STATUS  current
	DESCRIPTION
		"This table will map proprietary manufacturers ECUs into generic types defined on genericTypesTable."
	-- 1.3.6.1.3.8888.6
::= { obuMIB 6 }


mapTypeEntry OBJECT-TYPE
	SYNTAX  MapTypeEntry
	MAX-ACCESS not-accessible
	STATUS  current
	DESCRIPTION ""
	INDEX {
		mapTypeID }
	-- 1.3.6.1.3.8888.6.1
::= { mapTypeTable 1 }


MapTypeEntry ::= SEQUENCE {

	mapTypeID            Unsigned32,
	proprietaryTypeID    Unsigned32,
	genericMapTypeID     Unsigned32,
	sampleUnitMapID      Unsigned32,
	precision            INTEGER,
	maxSamplingFrequency Unsigned32,
	maxMapDelay          INTEGER,
	dataSource           OCTET STRING,
	interfaceSource      OCTET STRING }

mapTypeID OBJECT-TYPE
	SYNTAX  Unsigned32 (1..99999999)
	MAX-ACCESS read-only
	STATUS  current
	DESCRIPTION
		"This object will identify a certain Map Type"
	-- 1.3.6.1.3.8888.6.1.1
::= { mapTypeEntry 1 }

proprietaryTypeID OBJECT-TYPE
	SYNTAX  Unsigned32
	MAX-ACCESS read-only
	STATUS  current
	DESCRIPTION ""
	-- 1.3.6.1.3.8888.6.1.2
::= { mapTypeEntry 2 }


genericMapTypeID OBJECT-TYPE
	SYNTAX  Unsigned32
	MAX-ACCESS read-only
	STATUS  current
	DESCRIPTION
		"This object will contain the generic type of data recorded, this generic type of data is stored on the genericTypesTable"
	-- 1.3.6.1.3.8888.6.1.3
::= { mapTypeEntry 3 }


sampleUnitMapID OBJECT-TYPE
	SYNTAX  Unsigned32
	MAX-ACCESS read-only
	STATUS  current
	DESCRIPTION
		"This object will identify the unit in which samples are taken, this unit is stored on the sampleUnitsTable"
	-- 1.3.6.1.3.8888.6.1.4
::= { mapTypeEntry 4 }


precision OBJECT-TYPE
	SYNTAX  INTEGER (1..9999999 | 0)
	MAX-ACCESS read-only
	STATUS  current
	DESCRIPTION
		"This object will identify the precision of a particular sensor"
	-- 1.3.6.1.3.8888.6.1.5
::= { mapTypeEntry 5 }


maxSamplingFrequency OBJECT-TYPE
	SYNTAX  Unsigned32
	MAX-ACCESS read-only
	STATUS  current
	DESCRIPTION
		"This object will identify the maximum sampling frequency of a particular sensor"
	-- 1.3.6.1.3.8888.6.1.6
::= { mapTypeEntry 6 }


maxMapDelay OBJECT-TYPE
	SYNTAX  INTEGER
	MAX-ACCESS read-only
	STATUS  current
	DESCRIPTION
		"This object will identify the maximum delay of a particular sensor"
	-- 1.3.6.1.3.8888.6.1.7
::= { mapTypeEntry 7 }

dataSource OBJECT-TYPE
	SYNTAX  OCTET STRING
	MAX-ACCESS read-only
	STATUS  current
	DESCRIPTION
		"This object will identify the sensor, for example 'FMCW Sensor'"
	-- 1.3.6.1.3.8888.6.1.8
::= { mapTypeEntry 8 }


interfaceSource OBJECT-TYPE
	SYNTAX  OCTET STRING
	MAX-ACCESS read-only
	STATUS  current
	DESCRIPTION
		"This object will identify the interface from which data is being read, for example 'CAN 2.0'"
	-- 1.3.6.1.3.8888.6.1.9
::= { mapTypeEntry 9 }


genericTypesTable OBJECT-TYPE
	SYNTAX  SEQUENCE OF GenericTypesEntry
	MAX-ACCESS not-accessible
	STATUS  current
	DESCRIPTION
		"This table will contain a generic description of the type of data a certain sensor is generating, for example: 'Vehicle velocity'."
	-- 1.3.6.1.3.8888.7
::= { obuMIB 7 }


genericTypesEntry OBJECT-TYPE
	SYNTAX  GenericTypesEntry
	MAX-ACCESS not-accessible
	STATUS  current
	DESCRIPTION ""
	INDEX {
		genericTypeID }
	-- 1.3.6.1.3.8888.7.1
::= { genericTypesTable 1 }


GenericTypesEntry ::= SEQUENCE {

	genericTypeID   Unsigned32,
	typeDescription OCTET STRING }


genericTypeID OBJECT-TYPE
	SYNTAX  Unsigned32 (1..99999999)
	MAX-ACCESS read-only
	STATUS  current
	DESCRIPTION
		"This object will identify a certain type description"
	-- 1.3.6.1.3.8888.7.1.1
::= { genericTypesEntry 1 }

typeDescription OBJECT-TYPE
	SYNTAX  OCTET STRING
	MAX-ACCESS read-only
	STATUS  current
	DESCRIPTION
		"This object will contain generic information regarding the types of data that can be recorded"
	-- 1.3.6.1.3.8888.7.1.2
::= { genericTypesEntry 2 }



sampleUnitsTable OBJECT-TYPE
	SYNTAX  SEQUENCE OF SampleUnitsEntry
	MAX-ACCESS not-accessible
	STATUS  current
	DESCRIPTION
		"This table will contain the unit with which a sensor is recording data, for example: 'Km/h'.
		This will define the coding algorithm for the Precision object on the mapTypeTable."
	-- 1.3.6.1.3.8888.8
::= { obuMIB 8 }

sampleUnitsEntry OBJECT-TYPE
	SYNTAX  SampleUnitsEntry
	MAX-ACCESS not-accessible
	STATUS  current
	DESCRIPTION ""
	INDEX {
		sampleUnitID }
	-- 1.3.6.1.3.8888.8.1
::= { sampleUnitsTable 1 }


SampleUnitsEntry ::= SEQUENCE {

	sampleUnitID    Unsigned32,
	unitDescription OCTET STRING }

sampleUnitID OBJECT-TYPE
	SYNTAX  Unsigned32 (1..99999999)
	MAX-ACCESS read-only
	STATUS  current
	DESCRIPTION
		"This object will identify a certain unit description"
	-- 1.3.6.1.3.8888.8.1.1
::= { sampleUnitsEntry 1 }


unitDescription OBJECT-TYPE
	SYNTAX  OCTET STRING
	MAX-ACCESS read-only
	STATUS  current
	DESCRIPTION
		"This object will contain the units in which sensors record their data"
	-- 1.3.6.1.3.8888.8.1.2
::= { sampleUnitsEntry 2 }


errorTable OBJECT-TYPE
	SYNTAX  SEQUENCE OF ErrorEntry
	MAX-ACCESS not-accessible
	STATUS  current
	DESCRIPTION
		"This table will contain information regarding active error codes."
	-- 1.3.6.1.3.8888.9
::= { obuMIB 9 }

errorEntry OBJECT-TYPE
	SYNTAX  ErrorEntry
	MAX-ACCESS not-accessible
	STATUS  current
	DESCRIPTION
		""
	INDEX {
		errorID }
	-- 1.3.6.1.3.8888.9.1
::= { errorTable 1 }


ErrorEntry ::= SEQUENCE {

	errorID            Unsigned32,
	errorTimeStamp     OBUDateandTime,
	errorDescriptionID Unsigned32,
	errorUser          OCTET STRING,
	errorExpireTime    OCTET STRING }

errorID OBJECT-TYPE
	SYNTAX  Unsigned32 (1..99999999)
	MAX-ACCESS read-only
	STATUS  current
	DESCRIPTION
		"This object will identify all currently active reported errors"
	-- 1.3.6.1.3.8888.9.1.1
::= { errorEntry 1 }


errorTimeStamp OBJECT-TYPE
	SYNTAX  OBUDateandTime
	MAX-ACCESS read-only
	STATUS  current
	DESCRIPTION
		"This object will store the time in which an error was first reported"
	-- 1.3.6.1.3.8888.9.1.2
::= { errorEntry 2 }


errorDescriptionID OBJECT-TYPE
	SYNTAX  Unsigned32
	MAX-ACCESS read-only
	STATUS  current
	DESCRIPTION
		"This object will contain the description of a certain error, this description is stored on the errorDescriptionTable"
	-- 1.3.6.1.3.8888.9.1.3
::= { errorEntry 3 }


errorUser OBJECT-TYPE
	SYNTAX  OCTET STRING
	MAX-ACCESS read-only
	STATUS  current
	DESCRIPTION
		"This object will be used to store the user whose actions triggered an error"
	-- 1.3.6.1.3.8888.9.1.4
::= { errorEntry 4 }


errorExpireTime OBJECT-TYPE
	SYNTAX  OCTET STRING
	MAX-ACCESS read-only
	STATUS  current
	DESCRIPTION
		"This object will be used with errorTimeStamp to delete an error entry after the expire time has been passed"
	-- 1.3.6.1.3.8888.9.1.5 --
	::= { errorEntry 5 }


errorDescriptionTable OBJECT-TYPE
	SYNTAX  SEQUENCE OF ErrorDescriptionEntry
	MAX-ACCESS not-accessible
	STATUS  current
	DESCRIPTION
		"This table will be used to store all possible errors, both active or otherwise, and their descriptions."
	-- 1.3.6.1.3.8888.10
::= { obuMIB 10 }


errorDescriptionEntry OBJECT-TYPE
	SYNTAX  ErrorDescriptionEntry
	MAX-ACCESS not-accessible
	STATUS  current
	DESCRIPTION
		""
	INDEX {
		errorDescrID }
	-- 1.3.6.1.3.8888.10.1
::= { errorDescriptionTable 1 }


ErrorDescriptionEntry ::= SEQUENCE {

	errorDescrID Unsigned32,
	errorDescr   OCTET STRING,
	errorCode    Unsigned32 }


errorDescrID OBJECT-TYPE
	SYNTAX  Unsigned32 (1..99999999)
	MAX-ACCESS read-only
	STATUS  current
	DESCRIPTION
		"This object will identify a certain error description"
	-- 1.3.6.1.3.8888.10.1.1
::= { errorDescriptionEntry 1 }

errorDescr OBJECT-TYPE
	SYNTAX  OCTET STRING
	MAX-ACCESS read-only
	STATUS  current
	DESCRIPTION
		"This object will provide a generic description to the error being reported"
	-- 1.3.6.1.3.8888.10.1.2
::= { errorDescriptionEntry 2 }

errorCode OBJECT-TYPE
	SYNTAX  Unsigned32
	MAX-ACCESS read-only
	STATUS  current
	DESCRIPTION
		"This object will contain the current error code that was triggered by user action"
	-- 1.3.6.1.3.8888.11.1.3
	::= { errorDescriptionEntry 3 }

commandTemplateTable OBJECT-TYPE
	SYNTAX  SEQUENCE OF CommandTemplateEntry
	MAX-ACCESS not-accessible
	STATUS  current
	DESCRIPTION
		"This table will contain CAN command templates to be used when activating/deactivating actuators"
	-- 1.3.6.1.3.8888.11
::= { obuMIB 11 }



commandTemplateEntry OBJECT-TYPE
	SYNTAX  CommandTemplateEntry
	MAX-ACCESS not-accessible
	STATUS  current
	DESCRIPTION ""
	INDEX {
		commandTemplateID }
	-- 1.3.6.1.3.8888.11.1
	::= { commandTemplateTable 1 }


CommandTemplateEntry ::= SEQUENCE {

	commandTemplateID    Unsigned32,
	commandDescription   OCTET STRING,
	targetNode     		 OCTET STRING,
	commandTemplate 	 OCTET STRING }



commandTemplateID OBJECT-TYPE
	SYNTAX  Unsigned32 (1..99999999)
	MAX-ACCESS read-only
	STATUS  current
	DESCRIPTION
		"This object will identify a specific command template"
	-- 1.3.6.1.3.8888.11.1.1 --
	::= { commandTemplateEntry 1 }


commandDescription OBJECT-TYPE
	SYNTAX  OCTET STRING
	MAX-ACCESS read-only
	STATUS  current
	DESCRIPTION
		"This object will store a short description of what a command does"
	-- 1.3.6.1.3.8888.11.1.2 --
	::= { commandTemplateEntry 2 }


targetNode OBJECT-TYPE
	SYNTAX  OCTET STRING
	MAX-ACCESS read-only
	STATUS  current
	DESCRIPTION
		"This object will store the Node ID to which a command will be sent"
	-- 1.3.6.1.3.8888.11.1.3 --
	::= { commandTemplateEntry 3 }


commandTemplate OBJECT-TYPE
	SYNTAX  OCTET STRING
	MAX-ACCESS read-only
	STATUS  current
	DESCRIPTION
		"This object will store a template of a command in hex. eg: FF FF FF ** ** FF FF FF, where * indicate where user input will be placed"
	-- 1.3.6.1.3.8888.11.1.4 --
	::= { commandTemplateEntry 4 }


commandTable OBJECT-TYPE
	SYNTAX  SEQUENCE OF CommandEntry
	MAX-ACCESS not-accessible
	STATUS  current
	DESCRIPTION
		"This table will contain all commands that are to be sent into the CAN network"
	-- 1.3.6.1.3.8888.12
::= { obuMIB 12 }

commandEntry OBJECT-TYPE
	SYNTAX  CommandEntry
	MAX-ACCESS not-accessible
	STATUS  current
	DESCRIPTION ""
	INDEX {
		commandID }
	-- 1.3.6.1.3.8888.12.1
::= { commandTable 1 }


CommandEntry ::= SEQUENCE {

	commandID  		Unsigned32,
	templateID 		Unsigned32,
	commandInput    INTEGER,
	commandUser		OCTET STRING}


commandID OBJECT-TYPE
	SYNTAX  Unsigned32 (1..99999999)
	MAX-ACCESS read-create
	STATUS  current
	DESCRIPTION
		"This object will identify a certain command"
	-- 1.3.6.1.3.8888.12.1.1 --
	::= { commandEntry 1 }

templateID OBJECT-TYPE
	SYNTAX  Unsigned32
	MAX-ACCESS read-create
	STATUS  current
	DESCRIPTION
		"This object will be used to store the ID of the commandTemplate to be used in this command"
	-- 1.3.6.1.3.8888.12.1.2 --
	::= { commandEntry 2 }

commandInput OBJECT-TYPE
	SYNTAX  INTEGER
	MAX-ACCESS read-create
	STATUS  current
	DESCRIPTION
		"This object will be used to store the user inputs that are to be used in the command"
	-- 1.3.6.1.3.8888.12.1.3 --
	::= { commandEntry 3 }

commandUser OBJECT-TYPE
	SYNTAX  OCTET STRING
	MAX-ACCESS read-create
	STATUS  current
	DESCRIPTION
		"This object will store the username of the user that set this command"
	-- 1.3.6.1.3.8888.12.1.4 --
	::= { commandEntry 4 }

sensorGroup OBJECT-GROUP
	OBJECTS {
		requestID,
		requestMapID,
		savingMode,
		samplingFrequency,
		maxDelay,
		startTime,
		endTime,
		waitTime,
		durationTime,
		expireTime,
		lastSampleID,
		loopMode,
		nOfSamples,
		status,
		requestUser,
		requestControlID,
		requestControlMapID,
		settingMode,
		commitTime,
		endControlTime,
		durationControlTime,
		expireControlTime,
		valuesTableID,
		statusControl,
		statisticsID,
		durationTimeStatistics,
		nOfSamplesStatistics,
		minValue,
		maxValue,
		avgValue,
		capabilitiesID,
		setOfCapabilitiesID,
		specificCapabilitiesID,
		capabilitieValue,
		sampleID,
		requestSampleID,
		timeStamp,
		sampleFrequency,
		previousSampleID,
		mapTypeID,
		proprietaryTypeID,
		genericMapTypeID,
		sampleUnitMapID,
		precision,
		maxMapDelay,
		maxSamplingFrequency,
		interfaceSource,
		dataSource,
		genericTypeID,
		typeDescription,
		sampleUnitID,
		unitDescription,
		sampleRecordedValue,
		sampleType,
		mapTypeSamplesID,
		maxNOfSamples,
		requestStatisticsID,
		sampleCheckSum }
	STATUS  current
	DESCRIPTION
		"This group includes all objects related to sensor data retrieval"
	-- 1.3.6.1.3.8888.13 --
	::= { obuMIB 13 }

errorGroup OBJECT-GROUP
	OBJECTS {
		errorID,
		errorTimeStamp,
		errorDescriptionID,
		errorDescrID,
		errorDescr,
		errorUser,
		errorExpireTime,
		errorCode }
	STATUS  current
	DESCRIPTION
		"This group includes all objects related to errors"
	-- 1.3.6.1.3.8888.14 --
	::= { obuMIB 14 }


actuatorGroup OBJECT-GROUP
	OBJECTS {
		commandID,
		templateID,
		commandInput,
		commandUser,
		commandTemplateID,
		commandDescription,
		targetNode,
		commandTemplate }
	STATUS  current
	DESCRIPTION
		"This group includes all objects related to actuators"
	-- 1.3.6.1.3.8888.15 --
	::= { obuMIB 15 }


OBUDateandTime ::= OCTET STRING (SIZE (11 | 13))

END
